/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package PasteySysReq

import ScoreReq

ScoreReq.AssumedSystemReq ASR_RUST_CRATE {
    description = "The SW-platform shall support implementation of applications in the Rust programming language up to ASIL B."
    safety = ScoreReq.Asil.B
    version = 1
    rationale = "The system requires a Rust toolchain with stable language features to enable development of safety-critical software components"
}

ScoreReq.AssumedSystemReq ASR_RUST_COMPILER {
    description = "The Rust compiler used to build safety-critical applications shall be safety certified up to ASIL B."
    safety = ScoreReq.Asil.B
    version = 1
    rationale = "Safety-critical software development requires a qualified toolchain to ensure compiler-generated code meets functional safety requirements"
}
